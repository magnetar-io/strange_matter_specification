FME workspace StrangeMatter_BasicRoom_with_Level_1.fmw
Title: REVITNATIVE to NONE

Parameters:
- SourceDataset_REVITNATIVE = C:\Program Files\Autodesk\Revit 2023\Samples\rac_advanced_sample_project.rvt   # Revit Project File(s)
- outputpath = B:\FME to ECS\StrangeMatter_From_Revit_JSON_Folder\gltf and usd testing   # OutputPath

Readers:
- REVITNATIVE_1: REVITNATIVE from $(SourceDataset_REVITNATIVE)

Metadata.LevelInformation (reader REVITNATIVE_1)
    attributes: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
Architectural.Rooms (reader REVITNATIVE_1)
    attributes: ObjectId number(10,0), BuildingLevelElevation number(31,15), BuildingLevelRoomOffset number(31,15), BuildingLevelIsStory char(3), Dimensions.RoomArea number(31,15), BaseCategory char(5), BuildingLevel char(7), Category char(5), Constraints.BaseOffset number(31,15), Constraints.Level char(7), Constraints.LimitOffset number(31,15), Constraints.UpperLimit char(7), Dimensions.Area number(31,15), Dimensions.ComputationHeight number(31,15), Dimensions.Perimeter number(31,15), Dimensions.UnboundedHeight number(31,15), Dimensions.Volume char(0), Discipline char(13), ElementType char(8), EnergyAnalysis.ActualLightingLoad number(31,15), EnergyAnalysis.ActualLightingLoadperarea number(31,15), EnergyAnalysis.ActualPowerLoad number(31,15), EnergyAnalysis.ActualPowerLoadperarea number(31,15), EnergyAnalysis.AreaperPerson number(31,15), EnergyAnalysis.BaseLightingLoadon char(13), EnergyAnalysis.BasePowerLoadon char(13), EnergyAnalysis.CalculatedCoolingLoadperarea char(0), EnergyAnalysis.CalculatedHeatingLoadperarea char(0), EnergyAnalysis.HeatLoadValues char(13), EnergyAnalysis.LatentHeatGainperperson number(31,15),
      EnergyAnalysis.LightingLoadUnits char(13), EnergyAnalysis.NumberofPeople number(31,15), EnergyAnalysis.OccupancyUnit char(0), EnergyAnalysis.PlenumLightingContribution number(31,15), EnergyAnalysis.PowerLoadUnits char(13), EnergyAnalysis.SensibleHeatGainperperson number(31,15), EnergyAnalysis.SpecifiedLightingLoad number(31,15), EnergyAnalysis.SpecifiedLightingLoadperarea number(31,15), EnergyAnalysis.SpecifiedPowerLoad number(31,15), EnergyAnalysis.SpecifiedPowerLoadperarea number(31,15), EnergyAnalysis.TotalHeatGainperperson number(31,15), Family char(0), FamilyType char(0), IFCParameters.ExporttoIFC char(7), IFCParameters.ExporttoIFCAs char(0), IFCParameters.IFCPredefinedType char(0), IFCParameters.IfcGUID char(22), IdentityData.AssemblyCode char(0), IdentityData.AssemblyDescription char(0), IdentityData.Comments char(0), IdentityData.DesignOption char(2), IdentityData.Image char(0), IdentityData.Name char(7), IdentityData.Number char(1), IdentityData.RoomName char(7), IdentityData.RoomNumber char(1), IdentityData.TypeName char(0), InExteriorShell char(3), Mechanical-Flow.CalculatedSupplyAirflowperarea char(0), Other.Category char(5),
      Other.FamilyName char(0), Other.PhaseId char(16), Phasing.Phase char(16), UniqueId char(45), WorksetName char(8)
    -> UniqueIdentifierGenerator
AttributeFilter
    ATTR_NAME = BuildingLevel
    ATTR_VALUES = <Empty>,<Missing>,<Null>,<Unfiltered>,01 - Entry Level,02 - Floor,03 - Floor
    01 - Entry Level -> 2DForcer_2
    02 - Floor -> 2DForcer_2
    03 - Floor -> 2DForcer_2
2DForcer_2
    2D -> DonutHoleExtractor
DonutHoleExtractor
    DEAGGREGATE_INPUT = Yes
    OUTERSHELL -> DuplicateFilter
VolumeCalculator
    MULT = 1
    SET_TRAIT = No
    VOLUME_ATTR = _volume
Metadata.FileInformation (reader REVITNATIVE_1)
    attributes: DocVer char(18), DocUpdate char(14), DocSize number(10,0), AuthorUsername char(0), CreatedBy char(14), CentralModelPath char(0), IsCentralModel boolean, IsCreatedLocally boolean, GUID char(36), ProjectUnit char(5), IdentityData.AssemblyCode char(0), IdentityData.AssemblyDescription char(0), IdentityData.Author char(0), IdentityData.BuildingName char(0), IdentityData.DesignOption char(2), IdentityData.OrganizationDescription char(0), IdentityData.OrganizationName char(0), IdentityData.TypeName char(0), Other.Category char(19), Other.ClientName char(0), Other.FamilyName char(0), Other.ProjectAddress char(0), Other.ProjectIssueDate char(0), Other.ProjectName char(0), Other.ProjectNumber char(0), Other.ProjectStatus char(0)
    -> AttributeManager_2
AttributeManager_2
    ATTR_TABLE = SET_TO RevitGUID (varchar(200)) = @Value(GUID)
    -> AttributeKeeper
AttributeKeeper
    CREATE_BULK_MODE_FEATURES = NO
    KEEP_ATTRS = RevitGUID,DocSize,DocUpdate,DocVer,GUID,IdentityData.BuildingName,IdentityData.OrganizationName,IdentityData.TypeName,Other.ClientName,Other.FamilyName,Other.ProjectName,CentralModelPath,IdentityData.Author,IdentityData.OrganizationDescription,Other.ProjectAddress,Other.ProjectIssueDate,Other.ProjectNumber,Other.ProjectStatus,ProjectUnit
    -> FeatureMerger [SUPPLIER]
    -> FeatureMerger_2 [SUPPLIER]
    -> FeatureMerger_3 [SUPPLIER]
    -> FeatureMerger_5 [SUPPLIER]
    -> FeatureMerger_4 [SUPPLIER]
FeatureWriter_Qauntities
    DATASET = $(outputpath)\@Value(EntityGUID)_@Value(ComponetGUID)_@Value(ComponentType)_@Value(Classification).json
    DATASET_ATTR = _dataset
    FEATURE_TYPE_LIST_ATTR = _feature_types
    FORMAT = JSON
    JSON_DESTINATION_DATASETTYPE_VALIDATION = Yes
    JSON_INDENT_SIZE = 0
    JSON_MAX_COORDINATE_PRECISION = 10
    JSON_PRETTY_PRINT = YES
    JSON_WRITER_CHARSET = UTF-8
    JSON_WRITE_BOM = No
    JSON_WRITE_FEATURE_TYPE_KEY = NO
    JSON_WRITE_GEOMETRY = NO
    TOTAL_FEATURES_WRITTEN_ATTR = _total_features_written
AttributeManager_10

Bookmark: Entty ID is the same for both components, per item
UniqueIdentifierGenerator
    UUID_ATTR = _ulid
    UUID_FORMAT = ULID
    -> AttributeKeeper_2
    -> GeometryRemover
    -> GeometryRemover_2
    -> AttributeKeeper_6
    -> AttributeKeeper_5

Bookmark: valu
AttributeKeeper_2
    CREATE_BULK_MODE_FEATURES = NO
    KEEP_ATTRS = IdentityData.Name,IdentityData.RoomName,IFCParameters.IfcGUID,UniqueId,_ulid,BuildingLevel,Constraints.Level
    -> AttributeFilter
    -> VolumeCalculator
DuplicateFilter
    INPUT_ORDERED_CHOICE = No
    KEYATTR = IFCParameters.IfcGUID
    UNIQUE -> GeometryExtractor
GeometryExtractor
    ATTR = PAYLOAD
    JSON_MAX_DIGITS = 7
    KIND_LONG = GeoJSON
    REMOVE_GEOMETRY = No
    -> AttributeManager_3
AttributeManager_3
    -> FeatureMerger [REQUESTOR]
FeatureMerger
    ATTR_ACCUM_MODE = Merge Supplier
    ATTR_CONFLICT_RES = Use Requestor
    IGNORE_NULLS = No
    JOIN_KEYS = . . AUTO
    MERGE_TYPE = Attributes Only
    PROCESS_DUPS = NO
    REJECT_NULL_MISSING_KEYS = No
    SUPPLIERS_FIRST = No
    MERGED -> StrangeMatter_Create_Single [BaseComponent_Input]
StrangeMatter_Create_Single
    author_id_user = email address
    author_user = user
    authuring_software = Revit2024
    classifcation_user = hok.room.net
    component_type_reference_user = www.hok.com/components/v1
    component_type_user = component.geojson.polygon
    context_user = myprojectdata.ifc5
    function_user = Instance
    payload_data_type_user = geojson
    BaseComponent_Output -> AttributeManager
AttributeManager
    ATTR_TABLE:
      SET_TO SourceData (varchar(200)) = $(SourceDataset_REVITNATIVE)
      SET_TO SourceDataDate (varchar(200)) = @Value(DocUpdate)
      SET_TO SourceDataID (varchar(200)) = @Value(RevitGUID)
      SET_TO SourceDateVersionId (varchar(200)) = @Value(GUID)
      SET_TO SourceDataItemId (varchar(200)) = @Value(UniqueId)
      SET_TO SourceDataItemVersionId (varchar(18)) = not real value...
      SET_TO EntityGUID (buffer) = @Value(IFCParameters.IfcGUID)
      SET_TO SemanticVersion (varchar(2)) = V1
      SET_TO DateCreated (varchar(200)) = @DateTimeNow()
      SET_TO Name (varchar(200)) = @Value(IdentityData.RoomName)
      SET_TO SequenceName (varchar(2)) = na
      SET_TO SequenceValue (varchar(2)) = na
      SET_TO Option (uint8) = 1
      SET_TO Phase (varchar(16)) = New Construction
      SET_TO Payload (json) = @Value(PAYLOAD)
      REMOVE ComponentHASH (char(16))
      REMOVE PayloadHASH (char(16))
      REMOVE IdentityData.Name (char(7))
      REMOVE IdentityData.RoomName (char(7))
      REMOVE RevitGUID (varchar(200))
      REMOVE DocVer (char(18))
      REMOVE DocUpdate (char(14))
      REMOVE DocSize (number(10,0))
      REMOVE IFCParameters.IfcGUID (char(22))
      REMOVE UniqueId (char(45))
      REMOVE PAYLOAD (buffer)
      SET_TO
      REMOVE GUID (char(36))
      REMOVE _ulid (char(26))
      REMOVE BuildingLevel (char(7))
      REMOVE Constraints.Level (char(7))
      REMOVE CentralModelPath (char(0))
      REMOVE ProjectUnit (char(5))
      REMOVE IdentityData.Author (char(0))
      REMOVE IdentityData.BuildingName (char(0))
      REMOVE IdentityData.OrganizationDescription (char(0))
      REMOVE IdentityData.OrganizationName (char(0))
      REMOVE IdentityData.TypeName (char(0))
      REMOVE Other.ClientName (char(0))
      REMOVE Other.FamilyName (char(0))
      REMOVE Other.ProjectAddress (char(0))
      REMOVE Other.ProjectIssueDate (char(0))
      REMOVE Other.ProjectName (char(0))
      REMOVE Other.ProjectNumber (char(0))
    USER_EXPOSED_ATTRIBUTES = SequenceGuid
    -> AttributeRenamer
Note: Rename for Elastic
AttributeRenamer
    ATTR_TABLE = RENAME_SET_DEFAULT Payload > payload_geojson
    KEEP_RENAMED_ONLY = no
    MISSING_INPUT_ATTRS = REMOVE
    -> FeatureWriter [Output]
FeatureWriter
    DATASET = $(outputpath)\@Value(EntityGUID)_@Value(ComponetGUID)_@Value(ComponentType)_@Value(Classification).json
    DATASET_ATTR = _dataset
    FEATURE_TYPE_LIST_ATTR = _feature_types
    FORMAT = JSON
    JSON_DESTINATION_DATASETTYPE_VALIDATION = Yes
    JSON_INDENT_SIZE = 0
    JSON_MAX_COORDINATE_PRECISION = 10
    JSON_PRETTY_PRINT = YES
    JSON_WRITER_CHARSET = UTF-8
    JSON_WRITE_BOM = No
    JSON_WRITE_FEATURE_TYPE_KEY = NO
    JSON_WRITE_GEOMETRY = NO
    TOTAL_FEATURES_WRITTEN_ATTR = _total_features_written

Bookmark: StrangeMatter.ID
GeometryRemover
    REMOVE_COORDSYS = No
    -> AttributeKeeper_3
AttributeKeeper_3
    CREATE_BULK_MODE_FEATURES = NO
    KEEP_ATTRS = IdentityData.Name,IdentityData.RoomName,IFCParameters.IfcGUID,UniqueId,_ulid,IdentityData.AssemblyCode,IdentityData.AssemblyDescription,IdentityData.Comments,IdentityData.DesignOption,IdentityData.Image,IdentityData.Number,IdentityData.RoomNumber,IdentityData.TypeName,BuildingLevel,BuildingLevelElevation,BuildingLevelIsStory,BuildingLevelRoomOffset,Constraints.Level
    -> FeatureMerger_2 [REQUESTOR]
FeatureMerger_2
    ATTR_ACCUM_MODE = Merge Supplier
    ATTR_CONFLICT_RES = Use Requestor
    IGNORE_NULLS = No
    JOIN_KEYS = . . AUTO
    MERGE_TYPE = Attributes Only
    PROCESS_DUPS = NO
    REJECT_NULL_MISSING_KEYS = No
    SUPPLIERS_FIRST = No
    MERGED -> AttributeManager_5
AttributeManager_5
    ATTR_TABLE:
      SET_TO PAYLOAD_CREATOR_ID (varchar(200)) = {
        "IdentityData.Comments":"@Value(IdentityData.Comments)",
        "IdentityData.RoomName":"@Value(IdentityData.RoomName)",
        "IdentityData.RoomNumber":"@Value(IdentityData.RoomNumber)",
        "BuildingLevel":"@Value(BuildingLevel)",
        "BuildingLevelElevation":"@Value(BuildingLevelElevation)",
        "BuildingLevelIsStory":"@Value(BuildingLevelIsStory)",
        "BuildingLevelRoomOffset":"@Value(BuildingLevelRoomOffset)",
        "Other.ProjectName":"@Value(Other.ProjectName)",
        "Other.ProjectNumber":"@Value(Other.ProjectNumber)",
        "Other.ProjectStatus":"@Value(Other.ProjectStatus)",
        "Other.ClientName":"@Value(Other.ClientName)",
        "IdentityData.BuildingName":"@Value(IdentityData.BuildingName)",
        "CentralModelPath":"@Value(CentralModelPath)"
        }
    NUM_PRIOR_FEATURES = 0
    NUM_SUBSEQUENT_FEATURES = 0
    -> StrangeMatter_Create_Single_2 [BaseComponent_Input]
StrangeMatter_Create_Single_2
    author_id_user = email address
    author_user = user
    authuring_software = Revit2024
    classifcation_user = hok.room.net
    component_type_reference_user = www.hok.com/components/v1
    component_type_user = component.strangematter.id
    context_user = myprojectdata.ifc5
    function_user = Instance
    payload_data_type_user = json
    BaseComponent_Output -> AttributeManager_4
AttributeManager_4
    ATTR_TABLE:
      SET_TO SourceData (varchar(200)) = $(SourceDataset_REVITNATIVE)
      SET_TO SourceDataDate (varchar(200)) = @Value(DocUpdate)
      SET_TO SourceDataID (varchar(200)) = @Value(RevitGUID)
      SET_TO SourceDateVersionId (varchar(200)) = @Value(GUID)
      SET_TO SourceDataItemId (varchar(200)) = @Value(UniqueId)
      SET_TO SourceDataItemVersionId (varchar(18)) = not real value...
      SET_TO EntityGUID (buffer) = @Value(_ulid)
      SET_TO SemanticVersion (varchar(2)) = V1
      SET_TO DateCreated (varchar(200)) = @DateTimeNow()
      SET_TO Name (varchar(200)) = @Value(IdentityData.RoomName)
      SET_TO SequenceName (varchar(2)) = na
      SET_TO SequenceValue (varchar(2)) = na
      SET_TO Option (uint8) = 1
      SET_TO Phase (varchar(16)) = New Construction
      RENAME_SET_VALUE Payload (json) = @Value(PAYLOAD_CREATOR_ID)
      REMOVE ComponentHASH (char(16))
      REMOVE PayloadHASH (char(16))
      REMOVE IdentityData.Name (char(7))
      REMOVE IdentityData.RoomName (char(7))
      REMOVE RevitGUID (varchar(200))
      REMOVE DocVer (char(18))
      REMOVE DocUpdate (char(14))
      REMOVE DocSize (number(10,0))
      REMOVE IFCParameters.IfcGUID (char(22))
      REMOVE UniqueId (char(45))
      SET_TO
      REMOVE GUID (char(36))
      REMOVE _ulid (char(26))
      REMOVE IdentityData.AssemblyCode (char(0))
      REMOVE IdentityData.AssemblyDescription (char(0))
      REMOVE IdentityData.Comments (char(0))
      REMOVE IdentityData.DesignOption (char(2))
      REMOVE IdentityData.Image (char(0))
      REMOVE IdentityData.Number (char(1))
      REMOVE IdentityData.RoomNumber (char(1))
      REMOVE IdentityData.TypeName (char(0))
      REMOVE PAYLOAD_CREATOR_ID (varchar(200))
      REMOVE BuildingLevelElevation (number(31,15))
      REMOVE BuildingLevelRoomOffset (number(31,15))
      REMOVE BuildingLevelIsStory (char(3))
      REMOVE BuildingLevel (char(7))
      REMOVE Constraints.Level (char(7))
      REMOVE IdentityData.BuildingName (char(0))
      REMOVE IdentityData.OrganizationName (char(0))
      REMOVE Other.ClientName (char(0))
      REMOVE Other.FamilyName (char(0))
      REMOVE Other.ProjectName (char(0))
      REMOVE CentralModelPath (char(0))
      REMOVE ProjectUnit (char(5))
      REMOVE IdentityData.Author (char(0))
      REMOVE IdentityData.OrganizationDescription (char(0))
      REMOVE Other.ProjectAddress (char(0))
      REMOVE Other.ProjectIssueDate (char(0))
      REMOVE Other.ProjectNumber (char(0))
      REMOVE Other.ProjectStatus (char(0))
    USER_EXPOSED_ATTRIBUTES = SequenceGuid
    -> FeatureWriter_2 [Output]
FeatureWriter_2
    DATASET = $(outputpath)\@Value(EntityGUID)_@Value(ComponetGUID)_@Value(ComponentType)_@Value(Classification).json
    DATASET_ATTR = _dataset
    FEATURE_TYPE_LIST_ATTR = _feature_types
    FORMAT = JSON
    JSON_DESTINATION_DATASETTYPE_VALIDATION = Yes
    JSON_INDENT_SIZE = 0
    JSON_MAX_COORDINATE_PRECISION = 10
    JSON_PRETTY_PRINT = YES
    JSON_WRITER_CHARSET = UTF-8
    JSON_WRITE_BOM = Yes
    JSON_WRITE_FEATURE_TYPE_KEY = NO
    JSON_WRITE_GEOMETRY = NO
    TOTAL_FEATURES_WRITTEN_ATTR = _total_features_written

Bookmark: HOK Qauntities
GeometryRemover_2
    REMOVE_COORDSYS = No
    -> AttributeKeeper_4
AttributeKeeper_4
    CREATE_BULK_MODE_FEATURES = NO
    KEEP_ATTRS = IFCParameters.IfcGUID,UniqueId,_ulid,Dimensions.Area,Dimensions.ComputationHeight,Dimensions.Perimeter,Dimensions.RoomArea,Dimensions.UnboundedHeight,Dimensions.Volume,IdentityData.Name,IdentityData.RoomName
    -> FeatureMerger_3 [REQUESTOR]
FeatureMerger_3
    ATTR_ACCUM_MODE = Merge Supplier
    ATTR_CONFLICT_RES = Use Requestor
    IGNORE_NULLS = No
    JOIN_KEYS = . . AUTO
    MERGE_TYPE = Attributes Only
    PROCESS_DUPS = NO
    REJECT_NULL_MISSING_KEYS = No
    SUPPLIERS_FIRST = No
    MERGED -> AttributeManager_7
AttributeManager_7
    ATTR_TABLE:
      SET_TO PAYLOAD_CREATOR_Qauntities (varchar(200)) = {
        "Dimensions.Area":"@Value(Dimensions.Area)",
        "Dimensions.ComputationHeight":"@Value(Dimensions.ComputationHeight)",
        "Dimensions.Perimeter":"@Value(Dimensions.Perimeter)",
        "Dimensions.RoomArea":"@Value(Dimensions.RoomArea)",
        "Dimensions.UnboundedHeight":"@Value(Dimensions.UnboundedHeight)",
        "Dimensions.Volume":"@Value(Dimensions.Volume)"
        }
      REMOVE Dimensions.Area (number(31,15))
      REMOVE Dimensions.ComputationHeight (number(31,15))
      REMOVE Dimensions.Perimeter (number(31,15))
      REMOVE Dimensions.UnboundedHeight (number(31,15))
      REMOVE Dimensions.Volume (char(0))
    NUM_PRIOR_FEATURES = 0
    NUM_SUBSEQUENT_FEATURES = 0
    -> StrangeMatter_Create_Single_3 [BaseComponent_Input]
StrangeMatter_Create_Single_3
    author_id_user = email address
    author_user = user
    authuring_software = Revit2024
    classifcation_user = hok.room.net
    component_type_reference_user = www.hok.com/components/v1
    component_type_user = component.hok.qauntities.room
    context_user = myprojectdata.ifc5
    function_user = Instance
    payload_data_type_user = json
    BaseComponent_Output -> AttributeManager_6
AttributeManager_6
    ATTR_TABLE:
      SET_TO SourceData (varchar(200)) = $(SourceDataset_REVITNATIVE)
      SET_TO SourceDataDate (varchar(200)) = @Value(DocUpdate)
      SET_TO SourceDataID (varchar(200)) = @Value(RevitGUID)
      SET_TO SourceDateVersionId (varchar(200)) = @Value(GUID)
      SET_TO SourceDataItemId (varchar(200)) = @Value(UniqueId)
      SET_TO SourceDataItemVersionId (varchar(18)) = not real value...
      SET_TO EntityGUID (buffer) = @Value(_ulid)
      SET_TO SemanticVersion (varchar(2)) = V1
      SET_TO DateCreated (varchar(200)) = @DateTimeNow()
      SET_TO Name (varchar(200)) = @Value(IdentityData.RoomName)
      SET_TO SequenceName (varchar(2)) = na
      SET_TO SequenceValue (varchar(2)) = na
      SET_TO Option (uint8) = 1
      SET_TO Phase (varchar(16)) = New Construction
      RENAME_SET_VALUE Payload (json) = @Value(PAYLOAD_CREATOR_Qauntities)
      REMOVE ComponentHASH (char(16))
      REMOVE PayloadHASH (char(16))
      REMOVE IdentityData.Name (char(7))
      REMOVE IdentityData.RoomName (char(7))
      REMOVE RevitGUID (varchar(200))
      REMOVE DocVer (char(18))
      REMOVE DocUpdate (char(14))
      REMOVE DocSize (number(10,0))
      REMOVE IFCParameters.IfcGUID (char(22))
      REMOVE UniqueId (char(45))
      REMOVE GUID (char(36))
      REMOVE _ulid (char(26))
      REMOVE Dimensions.RoomArea (number(31,15))
      REMOVE PAYLOAD_CREATOR_Qauntities (varchar(200))
      REMOVE CentralModelPath (char(0))
      REMOVE ProjectUnit (char(5))
      REMOVE IdentityData.Author (char(0))
      REMOVE IdentityData.BuildingName (char(0))
      REMOVE IdentityData.OrganizationDescription (char(0))
      REMOVE IdentityData.OrganizationName (char(0))
      REMOVE IdentityData.TypeName (char(0))
      REMOVE Other.ClientName (char(0))
      REMOVE Other.FamilyName (char(0))
      REMOVE Other.ProjectAddress (char(0))
      REMOVE Other.ProjectIssueDate (char(0))
      REMOVE Other.ProjectName (char(0))
      REMOVE Other.ProjectNumber (char(0))
      REMOVE Other.ProjectStatus (char(0))
    USER_EXPOSED_ATTRIBUTES = SequenceGuid
    -> FeatureWriter_Qauntities [Output]

Bookmark: Other Geometry - ignore
AttributeKeeper_6 [off]
    CREATE_BULK_MODE_FEATURES = NO
    KEEP_ATTRS = IdentityData.Name,IdentityData.RoomName,IFCParameters.IfcGUID,UniqueId,_ulid,BuildingLevel,Constraints.Level
    -> FeatureMerger_4 [REQUESTOR] [off]
AttributeKeeper_5 [off]
    CREATE_BULK_MODE_FEATURES = NO
    KEEP_ATTRS = IdentityData.Name,IdentityData.RoomName,IFCParameters.IfcGUID,UniqueId,_ulid,BuildingLevel,Constraints.Level
    -> FeatureMerger_5 [REQUESTOR] [off]
FeatureMerger_4 [off]
    ATTR_ACCUM_MODE = Merge Supplier
    ATTR_CONFLICT_RES = Use Requestor
    IGNORE_NULLS = No
    JOIN_KEYS = . . AUTO
    MERGE_TYPE = Attributes Only
    PROCESS_DUPS = NO
    REJECT_NULL_MISSING_KEYS = No
    SUPPLIERS_FIRST = No
    MERGED -> StrangeMatter_Create_Single_4 [BaseComponent_Input] [off]
StrangeMatter_Create_Single_4 [off]
    author_id_user = email address
    author_user = user
    authuring_software = Revit2024
    classifcation_user = ifc.space
    component_type_reference_user = www.hok.com/components/v1
    component_type_user = component.ifc5.gltf
    context_user = myprojectdata.ifc5
    function_user = Instance
    payload_data_type_user = json
    BaseComponent_Output -> AttributeManager_8 [off]
AttributeManager_8 [off]
    ATTR_TABLE:
      SET_TO SourceData (varchar(200)) = $(SourceDataset_REVITNATIVE)
      SET_TO SourceDataDate (varchar(200)) = @Value(DocUpdate)
      SET_TO SourceDataID (varchar(200)) = @Value(RevitGUID)
      SET_TO SourceDateVersionId (varchar(200)) = @Value(GUID)
      SET_TO SourceDataItemId (varchar(200)) = @Value(UniqueId)
      SET_TO SourceDataItemVersionId (varchar(18)) = not real value...
      SET_TO EntityGUID (buffer) = @Value(_ulid)
      SET_TO SemanticVersion (varchar(2)) = V1
      SET_TO DateCreated (varchar(200)) = @DateTimeNow()
      SET_TO Name (varchar(200)) = @Value(IdentityData.RoomName)
      SET_TO SequenceName (varchar(2)) = na
      SET_TO SequenceValue (varchar(2)) = na
      SET_TO Option (uint8) = 1
      SET_TO Phase (varchar(16)) = New Construction
      RENAME_SET_VALUE Payload (json)
      REMOVE ComponentHASH (char(16))
      REMOVE PayloadHASH (char(16))
      REMOVE IdentityData.Name (char(7))
      REMOVE IdentityData.RoomName (char(7))
      REMOVE RevitGUID (varchar(200))
      REMOVE DocVer (char(18))
      REMOVE DocUpdate (char(14))
      REMOVE DocSize (number(10,0))
      REMOVE IFCParameters.IfcGUID (char(22))
      REMOVE UniqueId (char(45))
      REMOVE GUID (char(36))
      REMOVE _ulid (char(26))
      REMOVE BuildingLevel (char(7))
      REMOVE Constraints.Level (char(7))
    USER_EXPOSED_ATTRIBUTES = SequenceGuid,Dimensions.RoomArea,PAYLOAD_CREATOR_Qauntities
    -> FeatureWrite_GLTF [NewFeatureType] [off]
    -> FeatureMerger_6 [REQUESTOR] [off]
FeatureWrite_GLTF: FeatureWriter [off]
    DATASET = B:\FME to ECS\StrangeMatter_From_Revit_JSON_Folder
    DATASET_ATTR = _dataset
    FEATURE_TYPE_LIST_ATTR = _feature_types
    FORMAT = GLTF
    GLTF_CROP_AND_ATLAS_TEXTURES = NO
    GLTF_DESTINATION_DATASETTYPE_VALIDATION = Yes
    GLTF_GEOMETRY_COMPRESSION = NO_COMPRESSION
    GLTF_GLTF_VARIANT = EMBEDDED
    GLTF_GLTF_VERSION = 2_0
    GLTF_INDENT_SIZE = 0
    GLTF_LOCAL_COORDSYS_TRANSFORMATION = OFFSET_CENTROID_TO_ORIGIN
    GLTF_MOVE_TO_LOCAL_COORDSYS = No
    GLTF_PRETTY_PRINT = YES
    GLTF_TEXTURE_FORMAT_CHOICES = TRADITIONAL
    GLTF_TEXTURE_OUTPUT_FORMAT = NONE
    SELECTED_PORTS = NewFeatureType
    TOTAL_FEATURES_WRITTEN_ATTR = _total_features_written
    NewFeatureType -> FeatureReader [INITIATOR] [off]
FeatureReader [off]
    ATTRIBUTES = JSONFeature,"asset.generator,asset.version,materials{}.name,materials{}.pbrMetallicRoughness.baseColorFactor{},materials{}.pbrMetallicRoughness.roughnessFactor,materials{}.pbrMetallicRoughness.metallicFactor,materials{}.alphaMode,meshes{}.primitives{}.attributes.POSITION,meshes{}.primitives{}.attributes.COLOR_0,meshes{}.primitives{}.indices,meshes{}.primitives{}.material,meshes{}.primitives{}.mode,nodes{}.mesh,scenes{}.nodes{},scene,accessors{}.bufferView,accessors{}.byteOffset,accessors{}.componentType,accessors{}.count,accessors{}.type,accessors{}.min{},accessors{}.max{},bufferViews{}.buffer,bufferViews{}.byteOffset,bufferViews{}.byteLength,bufferViews{}.target,buffers{}.uri,buffers{}.byteLength,json_fragment"
    ATTR_ACCUM_MODE = Merge Initiator and Result
    ATTR_CONFLICT_RES = Use Result
    ATTR_IGNORE_NULLS = No
    COMBINE_GEOM = Use Result
    DATASET = B:\FME to ECS\StrangeMatter_From_Revit_JSON_Folder\*.gltf
    FEATURETYPES = JSONFeature
    FORMAT = JSON
    JSON_DECODE_TEXT_STRINGS = Yes
    JSON_FEATURE_TYPE_KEY = json_featuretype
    JSON_FLATTEN_MODE = ALL_LEVELS
    JSON_GEOMETRY_FORMAT = None
    JSON_SAVE_FRAGMENTS = YES
    JSON_SCAN_MODE = AUTO
    JSON_USE_BASENAME_AS_DEFAULT_FEATURE_TYPE = No
    JSON_USE_SEARCH_ENVELOPE = NO
    ORDER_RESULTS = No
    OUTPUT_ADD_SCHEMA_ATTRIBUTES = NO
    OUTPUT_FEATURES_DISPLAY = Schema and Data Features
    JSONFeature -> FeatureMerger_6 [SUPPLIER] [off]
FeatureMerger_6 [off]
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = @Value(ComponetGUID) @Value(ComponetGUID) AUTO
    MERGE_TYPE = Attributes and Geometry
    PROCESS_DUPS = YES
    REJECT_NULL_MISSING_KEYS = No
    SUPPLIERS_FIRST = No
    MERGED -> FeatureWriter_Qauntities_2 [Output] [off]
FeatureWriter_Qauntities_2 [off]
    DATASET = $(outputpath)\@Value(EntityGUID)_@Value(ComponetGUID)_@Value(ComponentType)_@Value(Classification).json
    DATASET_ATTR = _dataset
    FEATURE_TYPE_LIST_ATTR = _feature_types
    FORMAT = JSON
    JSON_DESTINATION_DATASETTYPE_VALIDATION = Yes
    JSON_INDENT_SIZE = 0
    JSON_MAX_COORDINATE_PRECISION = 10
    JSON_PRETTY_PRINT = YES
    JSON_WRITER_CHARSET = UTF-8
    JSON_WRITE_BOM = No
    JSON_WRITE_FEATURE_TYPE_KEY = NO
    JSON_WRITE_GEOMETRY = NO
    TOTAL_FEATURES_WRITTEN_ATTR = _total_features_written
FeatureMerger_5 [off]
    ATTR_ACCUM_MODE = Merge Supplier
    ATTR_CONFLICT_RES = Use Requestor
    IGNORE_NULLS = No
    JOIN_KEYS = . . AUTO
    MERGE_TYPE = Attributes Only
    PROCESS_DUPS = NO
    REJECT_NULL_MISSING_KEYS = No
    SUPPLIERS_FIRST = No
    MERGED -> AttributeManager_12 [off]
AttributeManager_12 [off]
    NUM_PRIOR_FEATURES = 0
    NUM_SUBSEQUENT_FEATURES = 0
    USER_EXPOSED_ATTRIBUTES = Dimensions.Area,Dimensions.Volume
    -> StrangeMatter_Create_Single_5 [BaseComponent_Input] [off]
StrangeMatter_Create_Single_5 [off]
    author_id_user = email address
    author_user = user
    authuring_software = Revit2024
    classifcation_user = ifc.space
    component_type_reference_user = www.hok.com/components/v1
    component_type_user = component.other.usd
    context_user = myprojectdata.ifc5
    function_user = Instance
    payload_data_type_user = json
    BaseComponent_Output -> AttributeManager_11 [off]
AttributeManager_11 [off]
    ATTR_TABLE:
      SET_TO SourceData (varchar(200)) = $(SourceDataset_REVITNATIVE)
      SET_TO SourceDataDate (varchar(200)) = @Value(DocUpdate)
      SET_TO SourceDataID (varchar(200)) = @Value(RevitGUID)
      SET_TO SourceDateVersionId (varchar(200)) = @Value(GUID)
      SET_TO SourceDataItemId (varchar(200)) = @Value(UniqueId)
      SET_TO SourceDataItemVersionId (varchar(18)) = not real value...
      SET_TO EntityGUID (buffer) = @Value(_ulid)
      SET_TO SemanticVersion (varchar(2)) = V1
      SET_TO DateCreated (varchar(200)) = @DateTimeNow()
      SET_TO Name (varchar(200)) = @Value(IdentityData.RoomName)
      SET_TO SequenceName (varchar(2)) = na
      SET_TO SequenceValue (varchar(2)) = na
      SET_TO Option (uint8) = 1
      SET_TO Phase (varchar(16)) = New Construction
      RENAME_SET_VALUE Payload (json)
      REMOVE ComponentHASH (char(16))
      REMOVE PayloadHASH (char(16))
      REMOVE IdentityData.Name (char(7))
      REMOVE IdentityData.RoomName (char(7))
      REMOVE RevitGUID (varchar(200))
      REMOVE DocVer (char(18))
      REMOVE DocUpdate (char(14))
      REMOVE DocSize (number(10,0))
      REMOVE IFCParameters.IfcGUID (char(22))
      REMOVE UniqueId (char(45))
      REMOVE GUID (char(36))
      REMOVE _ulid (char(26))
      REMOVE Constraints.Level (char(7))
    USER_EXPOSED_ATTRIBUTES = SequenceGuid
    -> FeatureWriter_3 [Output] [off]
    -> FeatureMerger_7 [REQUESTOR] [off]
FeatureWriter_3 [off]
    DATASET = B:\FME to ECS\StrangeMatter_From_Revit_JSON_Folder\gltf and usd testing
    DATASET_ATTR = _dataset
    FEATURE_TYPE_LIST_ATTR = _feature_types
    FORMAT = USD
    TOTAL_FEATURES_WRITTEN_ATTR = _total_features_written
    USD_CONVERT_TO_METERS = YES
    USD_DATASET_FORMAT = DIRECTORY
    USD_DESTINATION_DATASETTYPE_VALIDATION = Yes
    USD_LOCAL_COORDSYS_TRANSFORMATION = OFFSET_CENTROID_TO_ORIGIN
    USD_MOVE_TO_LOCAL_COORDSYS = No
    USD_USD_FORMAT = USDA
    SUMMARY -> FeatureReader_2 [INITIATOR] [off]
FeatureReader_2 [off]
    ATTRIBUTES = text_line,"text_line_data,fme_geometry{0},fme_basename"
    ATTR_ACCUM_MODE = Only Use Result
    COMBINE_GEOM = Use Result
    DATASET = B:\FME to ECS\StrangeMatter_From_Revit_JSON_Folder\gltf and usd testing\*.usda
    FORMAT = TEXTLINE
    ORDER_RESULTS = No
    OUTPUT_ADD_SCHEMA_ATTRIBUTES = NO
    OUTPUT_FEATURES_DISPLAY = Schema and Data Features
    TEXTLINE_CREATE_FEATURE_TABLES_FROM_DATA = Yes
    TEXTLINE_ENCODING = windows-1252
    TEXTLINE_READ_WHOLE_FILE_AT_ONCE = YES
    TEXTLINE_TEXTLINE_EXPOSE_FORMAT_ATTRS = fme_basename,char(50)
    text_line -> FeatureMerger_7 [SUPPLIER] [off]
FeatureMerger_7 [off]
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = @Value(ComponetGUID) @Value(fme_basename) AUTO
    MERGE_TYPE = Attributes and Geometry
    PROCESS_DUPS = YES
    REJECT_NULL_MISSING_KEYS = No
    SUPPLIERS_FIRST = No
    MERGED -> AttributeManager_9 [off]
AttributeManager_9 [off]
    -> FeatureWriter_Qauntities_3 [Output] [off]
FeatureWriter_Qauntities_3 [off]
    DATASET = $(outputpath)\@Value(EntityGUID)_@Value(ComponetGUID)_@Value(ComponentType)_@Value(Classification).json
    DATASET_ATTR = _dataset
    FEATURE_TYPE_LIST_ATTR = _feature_types
    FORMAT = JSON
    JSON_DESTINATION_DATASETTYPE_VALIDATION = Yes
    JSON_INDENT_SIZE = 0
    JSON_MAX_COORDINATE_PRECISION = 10
    JSON_PRETTY_PRINT = YES
    JSON_WRITER_CHARSET = UTF-8
    JSON_WRITE_BOM = No
    JSON_WRITE_FEATURE_TYPE_KEY = NO
    JSON_WRITE_GEOMETRY = NO
    TOTAL_FEATURES_WRITTEN_ATTR = _total_features_written

FME custom transformer StrangeMatter_Create_Single

Parameters:
- component_type_user =   # Componenet Type
- component_type_reference_user =   # Component Type Reference
- author_user =   # Author
- authuring_software =   # Authuring Software
- author_id_user =   # "email address"%"some other id" Author ID
- context_user =   # Context
- function_user =   # Function
- classifcation_user =   # Classification
- payload_data_type_user =   # Payload Data Type

BaseComponent_Input (input)
    -> BaseComponent
BaseComponent: AttributeManager
    ATTR_TABLE:
      SET_TO ComponentType (varchar(200)) = $(component_type_user)
      SET_TO ComponentTypeReference (varchar(200)) = $(component_type_reference_user)
      SET_TO ComponentTypeGuid (varchar(14)) = FakeGUIDforNOW
      SET_TO ComponentVersion (uint8) = 0001
      SET_TO ComponentHash (varchar(200))
      SET_TO Author (varchar(200)) = $(author_user)
      SET_TO AuthorIdentifier (varchar(200)) = $(author_id_user)
      SET_TO Context (varchar(200)) = $(context_user)
      SET_TO Function (varchar(200)) = $(function_user)
      SET_TO ParentTypical (varchar(200))
      SET_TO ParentArchitype (varchar(200))
      SET_TO AuthuringSoftware (varchar(200)) = $(authuring_software)
      SET_TO SourceData (varchar(200))
      SET_TO SourceDataDate (varchar(200))
      SET_TO SourceDataID (varchar(200))
      SET_TO SourceDateVersionId (varchar(200))
      SET_TO SourceDataItemId (varchar(200))
      SET_TO SourceDataItemVersionId (varchar(200))
      SET_TO EntityGUID (varchar(200))
      SET_TO ComponetGUID (varchar(200)) = @UUID()
      SET_TO ComponentVersionGUID (varchar(200)) = @UUID()
      SET_TO SemanticVersion (real64)
      SET_TO VersionIncrement (varchar(200))
      SET_TO DateCreated (varchar(200)) = @DateTimeNow()
      SET_TO Name (varchar(200))
      SET_TO Classification (varchar(200)) = $(classifcation_user)
      SET_TO SequenceGUID (varchar(200))
      SET_TO SequenceName (varchar(200))
      SET_TO SequenceValue (varchar(200))
      SET_TO Option (varchar(200))
      SET_TO Phase (varchar(200))
      SET_TO Status (varchar(3)) = WIP
      SET_TO Active (uint8) = 1
      SET_TO ResponceToComponent (varchar(200))
      SET_TO PayloadHash (varchar(200))
      SET_TO HashDefinition (varchar(3)) = MD5
      SET_TO PayloadDataType (varchar(200)) = $(payload_data_type_user)
      SET_TO Payload (varchar(200))
      REMOVE $(component_type_user) (varchar(200))
    USER_EXPOSED_ATTRIBUTES = $(component_type_user)
    -> AttributeExposer
AttributeExposer
    ATTR_TABLE = ComponentType,,ComponentTypeReference,,ComponentTypeGuid,,ComponentVersion,,ComponentHash,,AuthorIdentifier,,Context,,Function,,ParentTypical,,ParentArchitype,,AuthuringSoftware,,SourceData,,SourceDataID,,SourceDataDate,,SourceDateVersionId,,SourceDataItemId,,SourceDataItemVersionId,,EntityGUID,,ComponetGUID,,ComponentVersionGUID,,SemanticVersion,,VersionIncrement,,DateCreated,,Name,,Classification,,SequenceGUID,,SequenceName,,SequenceValue,,Option,,Phase,,Status,,Active,,ResponceToComponent,,PayloadHash,,HashDefinition,,PayloadDataType,,Payload,
    -> Component_Definision_HASH_CRCCalculator_2
Component_Definision_HASH_CRCCalculator_2: CRCCalculator
    ALG_CHOICES = MD5
    CALC_ATTRS = ComponentType ComponentTypeGuid ComponentTypeReference ComponentVersion
    CRC_ATTR = ComponentHASH
    CRC_TYPE = ATTRIBUTES_ENCODED
    -> Payload_HASH_CRCCalculator
Payload_HASH_CRCCalculator: CRCCalculator
    ALG_CHOICES = MD5
    CALC_ATTRS = Payload
    CRC_ATTR = PayloadHASH
    CRC_TYPE = ATTRIBUTES_ENCODED
    -> AttributeManager
AttributeManager
    ATTR_TABLE:
      SET_TO ComponentHash (varchar(200)) = @Value(ComponentHASH)
      SET_TO PayloadHash (varchar(200)) = @Value(PayloadHASH)
      SET_TO Payload (varchar(200))
    -> BaseComponent_Output (output)
BaseComponent_Output (output)
